package AirspaceManagementIBD {
    doc /* PLACEHOLDER internal block diagram for the Airspace Management domain
     * (to-do-list.md §10, operational IBDs). Created 2026-09-27 (D-010) to hold what
     * was moved off the context diagram: links internal to one domain, and the
     * question of how `atc` relates to tower / TRACON / ARTCC.
     * Rendered by MyViews::airspaceManagementIbd. Definitions stay in
     * nas_sysml_package_definitions.sysml (methods §10.1); this file holds usages and
     * wiring only.
     */

    metadata def IBDVisible {
        doc /* Tag for elements the Airspace Management IBD view should render. */
    }

    part def AirspaceManagementInternals {
        private import NationalAirspaceSystem::AirspaceManagement::*;

        // TODO(review), carried over from the context diagram: `atc` sits beside `tracon`,
        // `artcc`, `atcscc`, `tmu` in AirspaceManagementDomain as if it were one more peer,
        // but it is really the umbrella for tower + TRACON + ARTCC controllers. Options:
        //   (a) replace `atc` with `tower`, `tracon`, `artcc` (the tower is ATC by function,
        //       although the model's ControlTower facility is a part of Airport);
        //   (b) keep `atc` and give AirTrafficControlSystem the three as sub-parts;
        //   (c) keep all flat and accept the overlap at context level only.
        // (b) keeps the context diagram's rendered `atc` endpoint unchanged while the IBD
        // opens it up; it needs `tracon` / `artcc` to move under AirTrafficControlSystem in the
        // definitions. Decided 2026-11-05 (D-038): (c), atc stays one box. Only its decision
        // support is opened up, for the studied exchange (D-040).
        #IBDVisible part airspaceMgmt: AirspaceManagementDomain {
            #IBDVisible part :>> atc {
                // IMPROVED ARCHITECTURE (D-019). Drawn here so the report can point at the
                // port the aircraft performance data would arrive on (owner's 2026-10-19
                // print, Section 3.6: "be able to point to the port that would have the I/O").
                #IBDVisible port :>> performanceShareIn;
                // D-040: the decision support inside atc, and the two links the "Case C
                // Conflict Resolve" sequence needs (its gaps G1 and G2).
                #IBDVisible part :>> decisionSupport {
                    #IBDVisible port :>> performanceShareIn;
                    #IBDVisible port :>> advisoriesOut;
                }
                #IBDVisible port :>> controllerPosition;
                #IBDVisible connection shareToDecisionSupport connect performanceShareIn to decisionSupport.performanceShareIn;
                #IBDVisible connection advisoriesToController connect decisionSupport.advisoriesOut to controllerPosition;
            }
            #IBDVisible part :>> tracon;
            #IBDVisible part :>> artcc;
            #IBDVisible part :>> atcscc;
            #IBDVisible part :>> tmu;
            #IBDVisible part :>> tfmAutomation;

            // Domain boundary (owner's 2026-10-19 print): inputs left, outputs right.
            in #IBDVisible port :>> surveillanceIn;
            in #IBDVisible port :>> flightPlansIn;
            in #IBDVisible port :>> requestsIn;
            out #IBDVisible port :>> clearancesOut;

            #IBDVisible connection surveillanceToAtc connect surveillanceIn to atc;
            #IBDVisible connection flightPlansToAtc connect flightPlansIn to atc;
            #IBDVisible connection requestsToAtc connect requestsIn to atc;
            #IBDVisible connection clearancesFromAtc connect atc to clearancesOut;
            #IBDVisible connection tfmTools connect atcscc to tfmAutomation;
        }

        // Inter-ATC connections (from the context diagram's notes, 2026-09-27)
        //   - ATCSCC to TMU:
        //      - Flow Evaluation Areas (FEAs) and Flow Constrained Areas (FCAs): which flights in
        //        the TMU's sectors are hit by a national constraint.   -> [A] 7210.3EE 18-8-4a3, 18-7-13
        //      - TMIs: GDPs and GSs. The ATCSCC issues the EDCTs (18-10-6e); the ARTCC TMU
        //        coordinates them: relays them, assigns from the DAS table in some modes, and
        //        requests revised EDCTs from the ATCSCC (18-10-7).   -> [A]
        //      - Slot assignments, capacity limits (arrival rates), modeling data. FSM is the
        //        TOOL they travel on, not the exchange (18-10-3).     -> [A]
        //   - TMU to ATCSCC:
        //      - Disruption events: convective weather, low visibility, wind shifts, runway
        //        closures, airport equipment failures, computer/software outages.
        //                                                    -> [A] 18-2-4a6, 18-5-4c. SWAP is
        //                                                       ATCSCC-led (18-16): the TMU reports
        //                                                       conditions, the ATCSCC decides.
        //      - Miles/minutes-in-trail: up to 10 MIT facility to facility; 25+ MIT needs a
        //        shared FEA; 40+ MIT needs a conference.     -> [A] 18-7-12, 18-7-13
        //      - Time-based management STATUS. TBFM is the TOOL. -> [A] 18-5-4c1, 18-6-9b, 18-6-11
        //      - Delay reports (15-min verbal, NTML updates, 45-min TMO, 90-min verbal)
        //                                                    -> [A] 18-5-12
        //      - Reroute requests via the NTML                -> [A] 18-5-11, 18-8-4a3
        //      - Runway configuration with AAR/ADR; MAP value changes (not MAP alerts)
        //                                                    -> [A] 18-5-4e1, 18-9-2b
        //   Medium for almost all of it: NTML, "in preference to other methods" (18-5-3), plus
        //   hotlines. NTML is FAA-internal, which is why it appears here and not on the
        //   context diagram's operator-facing links.

        // Boundary links (2026-10-19, owner's print). Each port stands for a context-diagram
        // link that crosses the domain boundary; the comment names it.
        comment about airspaceMgmt::surveillanceToAtc /* [A] ADS-B Out and secondary radar replies reach the controllers (atcSurveillance; JO 7110.65BB 5-1-2, 5-2-1). The broadcast is aircraftBroadcastState on the activity model. */
        comment about airspaceMgmt::flightPlansToAtc /* [A] Filed flight plans and amendments to the ARTCC host (aocFlightPlanFiling; JO 7210.3EE 6-5). */
        comment about airspaceMgmt::requestsToAtc /* [A] Crew requests, read-backs and reports by voice or datalink (atcToCrew, atcAircraftDatalink). */
        comment about airspaceMgmt::clearancesFromAtc /* [A] Clearances and instructions, including the conflict-resolution instruction (item AirspaceManagement::Clearance; atcToCrew). */
        comment about airspaceMgmt::tfmTools /* [A] The ATCSCC works through the TFM tools (TFMS, FSM, NTML, TBFM, DRT): media, not a party (D-007 absorbed; JO 7210.3EE 18-5-3, 18-10-3). The TMUs use the same tools; that link is not drawn. Owner's "?" on the 2026-10-19 print. */

        comment about airspaceMgmt::atc::shareToDecisionSupport /* [B] IMPROVED (D-019, D-040). The airline's performance share, passed from atc's boundary port to the decision support that uses it (HLR-ATC-08). */
        comment about airspaceMgmt::atc::advisoriesToController /* [A] Conflict alerts and scored resolution options from the decision support to the controller (EDST, JO 7110.65BB 13-1-1; HLR-ATC-02, HLR-ATC-10, HLR-ATC-11). */

        #IBDVisible connection trafficManagementInitiatives connect airspaceMgmt.atcscc to airspaceMgmt.tmu;
        comment about trafficManagementInitiatives /* [A] National <-> local traffic flow management.
             * ATCSCC -> TMU: FEA/FCA, TMIs (GDP, GS, AFP, CTOP, reroutes), EDCTs, slot/rate data.
             * TMU -> ATCSCC: component outages and disruptions, weather conditions, MIT >= 25
             *   (FEA) / >= 40 (conference), TBM status, delay reports, reroute requests, runway
             *   configuration and AAR/ADR, MAP value changes.
             * Medium: NTML (preferred), TFMS, FSM, hotlines/telcons (tools in tfmAutomation).
             * Authority: ATCSCC is the final approving authority for interfacility TMIs (18-2-3i);
             * TMUs keep local order (sector MIT, fix balancing; 18-2-3 NOTE).
             * Hierarchy the single tmu part stands for: tower -> TRACON TMU -> ARTCC TMU -> ATCSCC.
             * Intent chain: enterprise/NAS flow objectives -> ATC constraints.
             * Sources: JO 7210.3EE CHG 3 Ch. 18. */

        #IBDVisible connection sectorFlowRestrictions connect airspaceMgmt.tmu to airspaceMgmt.atc;
        comment about sectorFlowRestrictions /* [A] TMU <-> tactical controllers: how a TMI becomes the clearance the crew
             * receives.
             * TMU -> controllers: MIT/MINIT, metering times (TBFM), EDCT verification, departure
             *   release times, airborne reroutes (Route Amendment Dialog -> ERAM for the sector
             *   to issue; 18-7-4h5).
             * Controllers -> TMU: sector load, EDCT checks for departures, departure readiness
             *   outside the EDCT window.
             * Sources: JO 7110.65BB 4-3-4 (tower <-> TMU on EDCT and release times, ATCSCC via
             * the TMU); JO 7210.3EE 18-2-4 (TMUs direct flows in conjunction with the ATCSCC),
             * 18-7-4h5. */

        // TODO(missing), IBD level: controller <-> controller links (handoff, point-out, tower <-> TRACON
        // departure release; BB 5-4-x, catalog transitions 5, 7, 9, 10) once the atc umbrella
        // question above is decided.
    }
}
