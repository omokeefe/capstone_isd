package ExperimentResults {
    doc /* GENERATED by projects/nas-sos-capstone/simulation/experiment_scoring.py on
     * 2026-11-10; scenario base; truth-model fidelity actualMass.
     * Do not edit. One attribute usage per case: the option chosen and the measured
     * values the verification cases in nas_verification.sysml read (D-017, D-018). */
    private import ScalarValues::*;

    attribute caseAOption : String = "O10";
    attribute caseASystemDeltaFuelKg : Real = 41.2;
    attribute caseAInstructions : Integer = 2;
    attribute caseBOption : String = "O10";
    attribute caseBSystemDeltaFuelKg : Real = 41.2;
    attribute caseBInstructions : Integer = 2;
    attribute caseCOption : String = "O4";
    attribute caseCSystemDeltaFuelKg : Real = 12.4;
    attribute caseCInstructions : Integer = 2;
    attribute caseDOption : String = "O4";
    attribute caseDSystemDeltaFuelKg : Real = 12.4;
    attribute caseDInstructions : Integer = 2;
}
