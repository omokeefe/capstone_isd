package ConstituentSystemRequirements {
    doc /*
     * The tier below the system requirements: what each of the five constituent systems
     * of the NAS (D-007's modeled systems) shall do, with that system as the subject of
     * the sentence. The owner calls these HLRs. IDs are HLR-<system>-nn.
     *
     * DRAFT, 2026-10-11. Written by Claude at the owner's request (decision D-022), from
     * the owner's example sentence for the flight crew and the owner's notes on the two
     * marked-up prints. HLR-CRW-01 is the owner's sentence. Every requirement has
     * status = draft. Hand-reviewed by the owner on 2026-10-20 (D-031); edits made from
     * a question on that print say so in their rationale. HLR-ACF-06 is new. Only
     * in-study system requirements have an HLR: this tier is where the study's cut is
     * made (D-031).
     *
     * HOW TO READ ONE
     *  - The doc comment is the requirement.
     *  - objectiveStatement says, in one sentence, what the requirement is for.
     *  - parentRequirements names the system requirement(s) in
     *    requirements_nas_system.sysml that it comes from. Every system requirement has
     *    at least one requirement here, if in study, and every requirement here has a parent.
     *  - candidateMeans lists the different ways the objective can be achieved, where
     *    there is more than one: a rule of thumb, a low-fidelity model, a high-fidelity
     *    model, and a high-fidelity model that also has the airline's connection
     *    priority. These are the experiment's cases A, B, C and D.
     *  - meansScoredInExperiment is true for the 3 requirements whose means the
     *    experiment scores side by side (HLR-ATC-04, HLR-ATC-05, HLR-ATC-06). Their
     *    verification cases, one per means, are in nas_verification.sysml.
     *  - rationale says why the requirement is in the study (D-020).
     *
     * 31 requirements: 5 on flight crew, 7 on flight operations, 11 on air traffic control, 6 on aircraft, 2 on airport operations.
     * HLR-ATC-10 and HLR-ATC-11 are new, from the owner's hand review of 2026-11-05 (D-040).
     * Parts of the five systems with no requirement here are listed in
     * knowledge/models/requirements-and-traceability.md section 11, with the reason.
     * If that file and this one disagree, this one wins (D-006).
     *
     * Attribute schema: requirements_definitions.sysml.
     */

    package FlightCrewRequirements {
        doc /* Flight Crew (D-007 modeled system; part flightCrew.flightDeckCrew). */

        public import RequirementDefinitions::*;

        requirement <'HLR-CRW-01'> flightControlledAsCleared : ConstituentSystemRequirement {
            doc /* The flight crew shall safely control the flight from origin to destination, as
             * cleared by air traffic control with or without negotiation, and in collaboration
             * with flight operations.
             */
            :>> status = RequirementStatus::draft;
            :>> kind = RequirementKind::functional;
            :>> constituentSystem = "Flight crew";
            :>> objectiveStatement = "The aircraft flies the trajectory that was cleared, and only that one, unless safety requires otherwise.";
            :>> parentRequirements = (SystemLevelRequirements::OnboardExecution::conformanceToClearedPath, SystemLevelRequirements::ClearanceAndSeparation::captainMayDeviateForSafety, SystemLevelRequirements::FlightPlanningAndRelease::jointRelease);
            :>> verificationMethod = VerificationMethod::byDemonstration;
            :>> basis = EvidenceGrade::ownerExpertise;
            :>> evidenceRefs = "14 CFR 91.3";
            :>> rationale = "The owner's sentence (2026-10-11), with 'cleared by' for 'cleared with'. In the study: whatever resolution is chosen, it takes effect only when the crew flies it.";
        }

        requirement <'HLR-CRW-02'> unflyableClearanceRefused : ConstituentSystemRequirement {
            doc /* The flight crew shall accept a clearance only if the aircraft can fly it, and shall
             * answer 'unable' when it cannot.
             */
            :>> status = RequirementStatus::draft;
            :>> kind = RequirementKind::functional;
            :>> constituentSystem = "Flight crew";
            :>> objectiveStatement = "No clearance the aircraft cannot fly is flown.";
            :>> parentRequirements = SystemLevelRequirements::ClearanceAndSeparation::clearanceWithinAircraftCapability;
            :>> verificationMethod = VerificationMethod::byDemonstration;
            :>> basis = EvidenceGrade::literature;
            :>> evidenceRefs = "coppenbarger1999climbPrediction";
            :>> rationale = "In the study: this is how today's NAS catches a climb the aircraft is too heavy for. It costs a refused clearance and a second one, which the experiment counts as extra instructions.";
        }

        requirement <'HLR-CRW-03'> betterTrajectoryRequested : ConstituentSystemRequirement {
            doc /* The flight crew shall ask air traffic control for a change of route, altitude or
             * speed when the crew deems it beneficial, optionally in collaboration with the
             * dispatcher.
             */
            :>> status = RequirementStatus::draft;
            :>> kind = RequirementKind::functional;
            :>> constituentSystem = "Flight crew";
            :>> objectiveStatement = "What the aircraft knows about its own best altitude and speed reaches the controller.";
            :>> parentRequirements = (SystemLevelRequirements::ClearanceAndSeparation::crewRequestAnswered, SystemLevelRequirements::OnboardExecution::onboardPerformancePredictions);
            :>> verificationMethod = VerificationMethod::byDemonstration;
            :>> basis = EvidenceGrade::literature;
            :>> evidenceRefs = "engility2014tasarAlaska";
            :>> rationale = "In the study: a crew request is the only channel for this knowledge today, so it is what the proposed data share is compared with. Owner (hand review 2026-10-20): 'Why call out FMS?' The trigger is now the crew's judgement, optionally with dispatch (owner's words).";
        }

        requirement <'HLR-CRW-04'> dispatcherToldOfTrajectoryChanges : ConstituentSystemRequirement {
            doc /* The flight crew shall tell the dispatcher of each change to the cleared trajectory.
             */
            :>> status = RequirementStatus::draft;
            :>> kind = RequirementKind::interfaceRequirement;
            :>> constituentSystem = "Flight crew";
            :>> objectiveStatement = "The airline learns of a tactical intervention in time to re-plan.";
            :>> parentRequirements = (SystemLevelRequirements::InformationForTrajectoryDecisions::arrivalEstimateUpdates, SystemLevelRequirements::OnboardExecution::lowFuelPredictionAlert, SystemLevelRequirements::ClearanceAndSeparation::controllerCrewCommunicationPath);
            :>> verificationMethod = VerificationMethod::byInspection;
            :>> basis = EvidenceGrade::literature;
            :>> evidenceRefs = "seamster2011collabSystems";
            :>> rationale = "Owner (2026-10-11): the crew and the dispatchers are the ones who have to coordinate for the airline to be informed (SN-AIR-03). Owner (hand review 2026-10-20) struck the trigger (arrival time moved by more than 5 minutes, or fuel at the destination below the reserve) and ended the sentence: 'Period?' The 5-minute trigger stays on the parent SLR-INF-07 (seamster2011collabSystems). In the study: this is how the cost of a resolution becomes known to the airline that bears it.";
        }

        requirement <'HLR-CRW-05'> weightsAndCostIndexEnteredInFms : ConstituentSystemRequirement {
            doc /* The flight crew shall enter the load sheet weights and the released cost index into
             * the flight management system before departure.
             */
            :>> status = RequirementStatus::draft;
            :>> kind = RequirementKind::functional;
            :>> constituentSystem = "Flight crew";
            :>> objectiveStatement = "The flight management system predicts from the weight the aircraft actually has.";
            :>> parentRequirements = (SystemLevelRequirements::FlightPlanningAndRelease::preDepartureInformationToCrew, SystemLevelRequirements::OnboardExecution::onboardPerformancePredictions);
            :>> verificationMethod = VerificationMethod::byInspection;
            :>> basis = EvidenceGrade::ownerExpertise;
            :>> rationale = "Graded [SME] for the owner to confirm from industry experience. In the study: the actual weight exists on board because the crew puts it there; it is the figure the high-fidelity means would share. Owner (hand review 2026-10-20): 'EPP gives weight, if available. Dispatch has final fuel numbers, I believe, and planned burn.' That is, the ADS-C extended projected profile can carry the weight to the ground, and the dispatcher already holds the final fuel figures and the planned burn, so the weight need not come only from the crew's entry.";
        }
    }

    package FlightOperationsRequirements {
        doc /* Flight Operations (D-007 modeled system; part flightOperations.airlineOperationsCenter and its dispatcher, load planner and decision support). */

        public import RequirementDefinitions::*;

        requirement <'HLR-OPS-01'> flightPlannedFromAircraftPerformance : ConstituentSystemRequirement {
            doc /* Flight operations shall plan each flight's route, cruise altitude, cruise speed and
             * fuel load from a model of the performance of the aircraft assigned to it, with the
             * fuel reserve the operating rules require.
             */
            :>> status = RequirementStatus::draft;
            :>> kind = RequirementKind::functional;
            :>> constituentSystem = "Flight operations";
            :>> objectiveStatement = "Each aircraft enters cruise at an altitude, speed and weight chosen for that aircraft.";
            :>> parentRequirements = (SystemLevelRequirements::FlightPlanningAndRelease::flightPlanContent, SystemLevelRequirements::FlightPlanningAndRelease::flightPlanUsesAssignedAircraft, SystemLevelRequirements::FlightPlanningAndRelease::fuelReserve);
            :>> candidateMeans = (MeansOfAchievement::ruleOfThumb, MeansOfAchievement::lowFidelityModel, MeansOfAchievement::highFidelityModel);
            :>> verificationMethod = VerificationMethod::byAnalysis;
            :>> basis = EvidenceGrade::literature;
            :>> evidenceRefs = ("mori2022massCruise", "berry2011aocActors");
            :>> rationale = "Owner (hand review 2026-10-11): the performance model can be a rule of thumb per aircraft type, a low-fidelity model or a high-fidelity model, and the fuel reserve goes into the low-fidelity model's assumptions. The three are listed as means. The experiment does not score them here: it takes each aircraft's plan as given. In the study: the plan sets the level, speed and weight each aircraft has when the conflict occurs.";
        }

        requirement <'HLR-OPS-02'> flightPlanFiledByDispatcher : ConstituentSystemRequirement {
            doc /* The dispatcher shall file each flight's plan with air traffic control before
             * departure.
             */
            :>> status = RequirementStatus::draft;
            :>> kind = RequirementKind::interfaceRequirement;
            :>> constituentSystem = "Flight operations";
            :>> objectiveStatement = "The controller has the airline's intended route, altitude and speed.";
            :>> parentRequirements = SystemLevelRequirements::FlightPlanningAndRelease::flightPlanFiledWithAtc;
            :>> verificationMethod = VerificationMethod::byInspection;
            :>> basis = EvidenceGrade::normativeSource;
            :>> evidenceRefs = ("faa2025aim", "faa2025jo72103ee");
            :>> rationale = "In the study: the filed plan is all the controller knows of the airline's intent today. It is what the rule of thumb and the low-fidelity means decide with.";
        }

        requirement <'HLR-OPS-03'> releasePackageGivenToCrew : ConstituentSystemRequirement {
            doc /* Flight operations shall give the flight crew the dispatch release, flight plan,
             * weather, notices to airmen (NOTAMs) and load sheet before departure.
             */
            :>> status = RequirementStatus::draft;
            :>> kind = RequirementKind::interfaceRequirement;
            :>> constituentSystem = "Flight operations";
            :>> objectiveStatement = "The crew and the flight management system start from the plan and the actual weights.";
            :>> parentRequirements = SystemLevelRequirements::FlightPlanningAndRelease::preDepartureInformationToCrew;
            :>> verificationMethod = VerificationMethod::byInspection;
            :>> basis = EvidenceGrade::literature;
            :>> evidenceRefs = "seamster2011collabSystems";
            :>> rationale = "In the study: the load sheet is where the actual weight enters the aircraft.";
        }

        requirement <'HLR-OPS-04'> dispatcherReleasesWithCaptain : ConstituentSystemRequirement {
            doc /* The dispatcher shall release a flight only with the captain's agreement that it can
             * be flown safely as planned.
             */
            :>> status = RequirementStatus::draft;
            :>> kind = RequirementKind::functional;
            :>> constituentSystem = "Flight operations";
            :>> objectiveStatement = "The planned cruise level is one the dispatcher and the captain have both agreed the aircraft can fly.";
            :>> parentRequirements = SystemLevelRequirements::FlightPlanningAndRelease::jointRelease;
            :>> verificationMethod = VerificationMethod::byInspection;
            :>> basis = EvidenceGrade::normativeSource;
            :>> evidenceRefs = "14 CFR 121.533";
            :>> rationale = "Owner (2026-10-11): there is no question that a descent can be achieved; a climb is different, and the joint release is what leads to that conclusion in the rule-of-thumb case. The released plan vouches for the planned level and below, and for nothing above it. In the study: this is the reason the rule of thumb descends and does not climb.";
        }

        requirement <'HLR-OPS-05'> performanceShareProvided : ConstituentSystemRequirement {
            doc /* Flight operations shall make each flight's current aircraft state and
             * performance, and the airline's priorities for it, available to the party that
             * decides a change to that flight's trajectory.
             */
            :>> status = RequirementStatus::draft;
            :>> kind = RequirementKind::interfaceRequirement;
            :>> architectureState = ArchitectureState::improved; // D-018
            :>> constituentSystem = "Flight operations";
            :>> objectiveStatement = "The party deciding can tell what each aircraft can fly and what a change costs its airline.";
            :>> parentRequirements = SystemLevelRequirements::InformationForTrajectoryDecisions::decisionInformationToDecidingParty;
            :>> verificationMethod = VerificationMethod::byAnalysis;
            :>> basis = EvidenceGrade::literature;
            :>> evidenceRefs = ("schultz2012adaptiveClimb", "coppenbarger1999climbPrediction", "sheth2010creditsConcept");
            :>> rationale = "What the airline shares, stated at the level of the architecture. The three are the attributes of AirlinePerformanceShare in nas_sysml_package_definitions.sysml (D-019, abstracted by D-040); the experiment represents them as gross weight, cost index and delay margin (NasAnalysis::ExperimentPerformanceShare). Not done today (schultz2012adaptiveClimb, page 2). In the study: what separates cases C and D from case B. Confidentiality is an assumption (D-020). History: the owner's question of 2026-10-20 ('Also it's performance model. Abstract from CI & talk about a measure of the relative cost of flight time?') gave the earlier list; the owner's hand review of 2026-11-05 replaced 'gross weight' with 'aircraft state' and abstracted the list (D-040).";
        }

        requirement <'HLR-OPS-06'> flightRePlannedWithCrew : ConstituentSystemRequirement {
            doc /* The dispatcher shall re-plan the flight with its crew when a trajectory change puts
             * the arrival time, the fuel at the destination or flight safety at risk.
             */
            :>> status = RequirementStatus::draft;
            :>> kind = RequirementKind::functional;
            :>> constituentSystem = "Flight operations";
            :>> objectiveStatement = "A tactical intervention is absorbed by the airline's plan and not only by the one flight.";
            :>> parentRequirements = (SystemLevelRequirements::ClearanceAndSeparation::controllerCrewCommunicationPath, SystemLevelRequirements::InformationForTrajectoryDecisions::arrivalEstimateUpdates, SystemLevelRequirements::OnboardExecution::lowFuelPredictionAlert);
            :>> verificationMethod = VerificationMethod::byDemonstration;
            :>> basis = EvidenceGrade::literature;
            :>> evidenceRefs = "seamster2011collabSystems";
            :>> rationale = "The dispatcher's half of the coordination the owner named for SN-AIR-03 (2026-10-11); HLR-CRW-04 is the crew's half. In the study: context for case D, where a late flight with connections is the reason one aircraft's time is worth more than its fuel. 'Or flight safety' added by the owner (hand review 2026-10-20).";
        }

        requirement <'HLR-OPS-07'> fuelAndCo2ReportedByAirline : ConstituentSystemRequirement {
            doc /* Flight operations shall report each flight's fuel burned and its CO2 emitted at 3.16
             * kg of CO2 per kg of fuel.
             */
            :>> status = RequirementStatus::draft;
            :>> kind = RequirementKind::performance;
            :>> constituentSystem = "Flight operations";
            :>> objectiveStatement = "The fuel and CO2 effect of a trajectory change can be counted.";
            :>> parentRequirements = SystemLevelRequirements::MeasurementAndRecords::fuelAndCo2ReportedPerFlight;
            :>> verificationMethod = VerificationMethod::byAnalysis;
            :>> measureOfPerformance = "CO2 emitted per kg of fuel burned";
            :>> unitOfMeasure = "kg CO2 per kg fuel";
            :>> thresholdValue = 3.16;
            :>> basis = EvidenceGrade::normativeSource;
            :>> evidenceRefs = "icao2024icecMethodology";
            :>> rationale = "In the study: the experiment's fuel column and the CO2 figure derived from it (D-015).";
        }
    }

    package AirspaceManagementRequirements {
        doc /* Airspace Management (D-007 modeled system; parts airspaceManagement.atc, its decision support, and the en-route center). */

        public import RequirementDefinitions::*;

        requirement <'HLR-ATC-01'> separationKeptWithConformanceMargin : ConstituentSystemRequirement {
            doc /* Air traffic control shall keep each pair of aircraft it controls separated by at
             * least the applicable minimum, allowing for each aircraft's permitted deviation from
             * its cleared route, altitude and speed.
             */
            :>> status = RequirementStatus::draft;
            :>> kind = RequirementKind::performance;
            :>> constituentSystem = "Air traffic control";
            :>> objectiveStatement = "No loss of separation.";
            :>> parentRequirements = (SystemLevelRequirements::ClearanceAndSeparation::separationMinimaMaintained, SystemLevelRequirements::OnboardExecution::conformanceToClearedPath);
            :>> verificationMethod = VerificationMethod::byAnalysis;
            :>> measureOfPerformance = "lateral and vertical distance between each pair of aircraft";
            :>> unitOfMeasure = "NM and ft";
            :>> basis = EvidenceGrade::normativeSource;
            :>> evidenceRefs = "faa2025jo711065bb";
            :>> rationale = "Owner (hand review 2026-10-10): conformance has to be accounted for in the separation requirements. In the study: the hard constraint on every resolution option, whichever means chooses it.";
        }

        requirement <'HLR-ATC-02'> controllerAlertedToPredictedConflict : ConstituentSystemRequirement {
            doc /* ATC decision support shall alert the sector controller to each predicted loss of
             * separation before it occurs.
             */
            :>> status = RequirementStatus::draft;
            :>> kind = RequirementKind::functional;
            :>> constituentSystem = "Air traffic control";
            :>> objectiveStatement = "The controller has time to choose a resolution and not only to react.";
            :>> parentRequirements = SystemLevelRequirements::ClearanceAndSeparation::conflictsPredicted;
            :>> verificationMethod = VerificationMethod::byAnalysis;
            :>> basis = EvidenceGrade::literature;
            :>> evidenceRefs = "engility2014tasarAlaska";
            :>> rationale = "In the study: the starting event of the experiment. No look-ahead time is set; engility2014tasarAlaska page 9 uses eight minutes in its own model.";
        }

        requirement <'HLR-ATC-03'> filedIntentShownToController : ConstituentSystemRequirement {
            doc /* The en-route center shall inform the sector controller of each aircraft's filed
             * route, requested altitude and requested speed before the aircraft enters the sector.
             */
            :>> status = RequirementStatus::draft;
            :>> kind = RequirementKind::interfaceRequirement;
            :>> constituentSystem = "Air traffic control";
            :>> objectiveStatement = "The controller knows where each aircraft intends to go.";
            :>> parentRequirements = SystemLevelRequirements::InformationForTrajectoryDecisions::filedIntentToSectorController;
            :>> verificationMethod = VerificationMethod::byInspection;
            :>> basis = EvidenceGrade::normativeSource;
            :>> evidenceRefs = "faa2025jo711065bb";
            :>> rationale = "In the study: together with type, level and speed, this is the whole of 'today's information' that the rule of thumb decides with (case A). 'Inform ... of' for 'show' by the owner (hand review 2026-10-20).";
        }

        requirement <'HLR-ATC-04'> conflictResolvedWithFlyableClearance : ConstituentSystemRequirement {
            doc /* Air traffic control shall resolve each predicted conflict with a clearance that
             * every aircraft it moves can fly.
             */
            :>> status = RequirementStatus::draft;
            :>> kind = RequirementKind::designConstraint;
            :>> architectureState = ArchitectureState::baseline; // D-018; baseline since D-040
            :>> constituentSystem = "Air traffic control";
            :>> objectiveStatement = "The conflict is resolved by the first clearance issued, with no 'unable' and no second attempt.";
            :>> parentRequirements = (SystemLevelRequirements::ClearanceAndSeparation::clearanceWithinAircraftCapability, SystemLevelRequirements::ClearanceAndSeparation::separationMinimaMaintained);
            :>> candidateMeans = (MeansOfAchievement::ruleOfThumb, MeansOfAchievement::lowFidelityModel, MeansOfAchievement::highFidelityModel, MeansOfAchievement::highFidelityModelWithConnections);
            :>> meansScoredInExperiment = true;
            :>> verificationMethod = VerificationMethod::byAnalysis;
            :>> measureOfPerformance = "whether the chosen option is flyable under the truth model";
            :>> unitOfMeasure = "yes or no";
            :>> basis = EvidenceGrade::literature;
            :>> evidenceRefs = ("coppenbarger1999climbPrediction", "engility2014tasarAlaska");
            :>> rationale = "Four means of knowing what an aircraft can fly, scored in the experiment. Rule of thumb: descend, and offer a climb only at or below FL350 (D-013, from engility2014tasarAlaska page 8; the joint release in HLR-OPS-04 is why a descent is safe to assume). Low-fidelity model: one nominal weight per aircraft type (coppenbarger1999climbPrediction). High-fidelity model: each aircraft's own weight, shared under HLR-OPS-05. The fourth adds connection priority, which does not change what can be flown. The truth model's thrust check (NasAnalysis::CanHoldLevel) says whether the option each means chose was flyable. Baseline since 2026-11-05 (owner's hand review, D-040: 'This is currently met today w/ auto-Descent assumption'): the rule's descent is a clearance every aircraft can fly. What today's NAS cannot do is confirm a climb above FL350 without the aircraft's weight (SLR-INF-02; HLR-ATC-10 since D-043).";
        }

        requirement <'HLR-ATC-05'> lowestImpactResolutionChosen : ConstituentSystemRequirement {
            doc /* Air traffic control shall choose, among the viable resolution options, the one
             * with the lowest estimated impact on the systems involved.
             */
            :>> status = RequirementStatus::draft;
            :>> kind = RequirementKind::performance;
            :>> architectureState = ArchitectureState::baseline; // D-018; baseline since D-044
            :>> constituentSystem = "Air traffic control";
            :>> objectiveStatement = "The option issued is the one the deciding party estimates has the lowest impact on the systems involved.";
            :>> parentRequirements = SystemLevelRequirements::ClearanceAndSeparation::lowestImpactResolution;
            :>> candidateMeans = (MeansOfAchievement::ruleOfThumb, MeansOfAchievement::lowFidelityModel, MeansOfAchievement::highFidelityModel, MeansOfAchievement::highFidelityModelWithConnections);
            :>> meansScoredInExperiment = true;
            :>> verificationMethod = VerificationMethod::byAnalysis;
            :>> measureOfPerformance = "whether the option chosen has the lowest impact by the case's own estimate; the truth model's impact of the choice is reported, not graded";
            :>> unitOfMeasure = "yes or no; kg and USD per conflict reported";
            :>> basis = EvidenceGrade::literature;
            :>> evidenceRefs = ("schultz2012adaptiveClimb", "mori2022massCruise", "kirwan2001coraStrategies");
            :>> rationale = "The last of the three HLRs SLR-CLR-13 decomposes into (owner's hand review 2026-11-05, D-040): determine the viable options (HLR-ATC-10), determine the impact of each (HLR-ATC-11), choose the lowest. 'Shall', as its parent, since the same review. Kept improved then: in the owner's words it 'is not truly met, but an approximation is pursued, at least conceptually.' Baseline since 2026-11-10 (owner, D-044): 'lowest estimated impact', so each means meets it by its own estimate; the truth model's impact of each means' choice is reported side by side, not graded. Four means of choosing, scored in the experiment. Rule of thumb: one descent, by the controller's rule (rantanen2012conflictManeuvers: 23 of 36 observed cases). Low-fidelity model: lowest estimated impact with one nominal performance per type, which cannot tell two aircraft of one type apart. High-fidelity model: lowest estimated impact with each aircraft's shared state, performance and priorities. High-fidelity model plus connections: the same, with the airline's connection priority. One truth model scores what each means chose. Owner (hand review 2026-10-20) circled 'aircraft': 'systems?' The parent SLR-CLR-13 still says 'the aircraft involved'.";
        }

        requirement <'HLR-ATC-06'> conflictResolvedWithinWorkload : ConstituentSystemRequirement {
            doc /* Air traffic control shall resolve each predicted conflict within the number of
             * instructions the sector team can sustain.
             */
            :>> status = RequirementStatus::draft;
            :>> kind = RequirementKind::performance;
            :>> constituentSystem = "Air traffic control";
            :>> objectiveStatement = "Controller workload stays under its ceiling whichever means chooses the resolution.";
            :>> parentRequirements = SystemLevelRequirements::ClearanceAndSeparation::instructionsWithinSustainableWorkload;
            :>> candidateMeans = (MeansOfAchievement::ruleOfThumb, MeansOfAchievement::lowFidelityModel, MeansOfAchievement::highFidelityModel, MeansOfAchievement::highFidelityModelWithConnections);
            :>> meansScoredInExperiment = true;
            :>> verificationMethod = VerificationMethod::byAnalysis;
            :>> measureOfPerformance = "instructions issued plus follow-up instructions, per conflict";
            :>> unitOfMeasure = "count";
            :>> basis = EvidenceGrade::literature;
            :>> evidenceRefs = ("rantanen2012conflictManeuvers", "kirwan2001coraStrategies");
            :>> rationale = "No ceiling is set, as on the parent SLR-CLR-15, so the experiment reports the count for each means and does not pass or fail it. In the study: the experiment's workload column, which is how a cheaper resolution that takes more instructions is shown for what it is.";
        }

        requirement <'HLR-ATC-07'> crewRequestAnsweredByController : ConstituentSystemRequirement {
            doc /* Air traffic control shall answer each flight crew request for a route, altitude or
             * speed change with an approval, an amended clearance or 'unable'.
             */
            :>> status = RequirementStatus::draft;
            :>> kind = RequirementKind::functional;
            :>> constituentSystem = "Air traffic control";
            :>> objectiveStatement = "A crew request is never left open.";
            :>> parentRequirements = SystemLevelRequirements::ClearanceAndSeparation::crewRequestAnswered;
            :>> verificationMethod = VerificationMethod::byDemonstration;
            :>> basis = EvidenceGrade::normativeSource;
            :>> evidenceRefs = ("faa2025jo711065bb", "engility2014tasarAlaska");
            :>> rationale = "JO 7110.65BB paragraph 2-1-18, as recorded in evidence/literature-notes/summaries/5 - faa2025jo711065bb.md (which also allows 'stand by'). In the study: the controller's half of the request channel in HLR-CRW-03. Owner (hand review 2026-10-20): 'Confirm ATC unable. I think it's actually deny/negative.' Checked against the summary only: 2-1-18 lists '(request) APPROVED', approved with restrictions, 'UNABLE' (with a reason if time permits) and 'STAND BY'. 'Unable' is kept; the order itself was not re-read.";
        }

        requirement <'HLR-ATC-08'> performanceShareUsedInResolution : ConstituentSystemRequirement {
            doc /* ATC decision support shall use the best information available to it about each
             * flight, including what the flight's airline shares.
             */
            :>> status = RequirementStatus::draft;
            :>> kind = RequirementKind::functional;
            :>> architectureState = ArchitectureState::baseline; // D-018; baseline since D-046
            :>> constituentSystem = "Air traffic control";
            :>> candidateMeans = (MeansOfAchievement::ruleOfThumb, MeansOfAchievement::lowFidelityModel, MeansOfAchievement::highFidelityModel, MeansOfAchievement::highFidelityModelWithConnections);
            :>> objectiveStatement = "The shared information changes the decision and does not only arrive.";
            :>> parentRequirements = SystemLevelRequirements::InformationForTrajectoryDecisions::decisionInformationToDecidingParty;
            :>> verificationMethod = VerificationMethod::byAnalysis;
            :>> basis = EvidenceGrade::literature;
            :>> evidenceRefs = ("schultz2012adaptiveClimb", "coppenbarger1999climbPrediction");
            :>> rationale = "The receiving end of HLR-OPS-05 (D-019: decision support is owned by the system that decides, D-012). Tagged improved until 2026-11-10 ('not done today'). Baseline since then (owner, D-046): 'It uses the best info available, right? That's what it has with the limited info interface.' Each means meets it with what it receives: the rule of thumb and the low-fidelity model use what air traffic control receives today; the high-fidelity means use the airline's share. What today's NAS lacks is the share itself (HLR-OPS-05). In the study: the difference between case B and cases C and D. Owner (hand review 2026-10-20): 'Why not use the best information available to them?' Narrowed in the owner's hand review of 2026-11-05 (D-040): the list of items is struck, and what the information is used for (which options can be flown, what each costs) is now HLR-ATC-10 and HLR-ATC-11, so the three do not overlap. This one states the input only.";
        }

        requirement <'HLR-ATC-09'> clearancesRecorded : ConstituentSystemRequirement {
            doc /* Air traffic control shall record each clearance it issues with the issuing facility
             * and the time.
             */
            :>> status = RequirementStatus::draft;
            :>> kind = RequirementKind::functional;
            :>> constituentSystem = "Air traffic control";
            :>> objectiveStatement = "A resolution can be examined after the fact.";
            :>> parentRequirements = SystemLevelRequirements::MeasurementAndRecords::trajectoryDecisionsRecorded;
            :>> verificationMethod = VerificationMethod::byInspection;
            :>> basis = EvidenceGrade::normativeSource;
            :>> evidenceRefs = "faa2025jo72103ee";
            :>> rationale = "In the study: the record is what a real-world version of the experiment's instruction count would be taken from.";
        }

        requirement <'HLR-ATC-10'> viableOptionsDetermined : ConstituentSystemRequirement {
            doc /* Air traffic control shall determine, for each predicted conflict, the resolution
             * options it can confirm restore separation safely and can be flown by each aircraft
             * it moves.
             */
            :>> status = RequirementStatus::draft;
            :>> kind = RequirementKind::functional;
            :>> architectureState = ArchitectureState::baseline; // D-040; baseline since D-043
            :>> constituentSystem = "Air traffic control";
            :>> objectiveStatement = "Every option that reaches the choice is one ATC can confirm is safe and can be flown.";
            :>> parentRequirements = SystemLevelRequirements::ClearanceAndSeparation::lowestImpactResolution;
            :>> candidateMeans = (MeansOfAchievement::ruleOfThumb, MeansOfAchievement::lowFidelityModel, MeansOfAchievement::highFidelityModel, MeansOfAchievement::highFidelityModelWithConnections);
            :>> meansScoredInExperiment = true;
            :>> verificationMethod = VerificationMethod::byAnalysis;
            :>> measureOfPerformance = "options treated as viable that the case's own information does not confirm; the number of options found is reported";
            :>> unitOfMeasure = "count (met at zero)";
            :>> basis = EvidenceGrade::literature;
            :>> evidenceRefs = ("engility2014tasarAlaska", "coppenbarger1999climbPrediction");
            :>> rationale = "The first of the three HLRs SLR-CLR-13 decomposes into (owner's hand review 2026-11-05, D-040: 'Determine options that are viable, determine cost of each, choose lowest impact'). Baseline since 2026-11-08 (owner, D-043): not every option has to be considered, only those the controller can confirm are safe, which is why a climb above FL350 is not offered without the aircraft's weight (D-013, engility2014tasarAlaska page 8). Today's controller meets it by the rule of thumb. Four means, scored in the experiment. Rule of thumb (case A): descents only. Low-fidelity model (case B): adds vectors and speed changes, and climbs only at or below FL350, checked with one nominal performance per type. High-fidelity model (case C) and with connections (case D): adds the climbs each aircraft's shared weight shows it can hold. The requirement asks that only confirmed options are offered; how many each means can confirm depends on its information (SLR-INF-02, HLR-ATC-08) and is reported, not passed or failed. Distinct from HLR-ATC-04, which checks the clearance issued against the truth model. Was 'ATC decision support shall determine, for each predicted conflict, every resolution option that restores separation and that each aircraft it moves can fly', tagged improved, verified against the truth model's set (D-040).";
        }

        requirement <'HLR-ATC-11'> optionImpactDetermined : ConstituentSystemRequirement {
            doc /* Air traffic control shall determine the impact of each resolution option it
             * considers on the systems involved.
             */
            :>> status = RequirementStatus::draft;
            :>> kind = RequirementKind::functional;
            :>> architectureState = ArchitectureState::baseline; // D-040; baseline since D-042
            :>> constituentSystem = "Air traffic control";
            :>> objectiveStatement = "The options considered are weighed by their impact, at whatever fidelity the information allows.";
            :>> parentRequirements = SystemLevelRequirements::ClearanceAndSeparation::lowestImpactResolution;
            :>> candidateMeans = (MeansOfAchievement::ruleOfThumb, MeansOfAchievement::lowFidelityModel, MeansOfAchievement::highFidelityModel, MeansOfAchievement::highFidelityModelWithConnections);
            :>> meansScoredInExperiment = true;
            :>> verificationMethod = VerificationMethod::byAnalysis;
            :>> measureOfPerformance = "whether the options considered are compared by an estimate of their impact";
            :>> unitOfMeasure = "yes or no";
            :>> basis = EvidenceGrade::literature;
            :>> evidenceRefs = ("schultz2012adaptiveClimb", "mori2022massCruise");
            :>> rationale = "The second of the three HLRs SLR-CLR-13 decomposes into (owner's hand review 2026-11-05, D-040). Baseline since 2026-11-08 (owner [SME], D-042): the controller does it today, poorly. Rules of thumb remove the climbs before any assessment is made, and the controller then weighs the impact of what is left (a turn against a descent) without the aircraft's performance (SLR-INF-02). The requirement asks that impact be estimated, not how accurately, so no tolerance is set: how much the estimate is worth depends on how close the information it rests on is to reality, and that is what the study compares. Four means, scored in the experiment. Rule of thumb (case A): the controller's judgment, after the climb rule (D-013). Low-fidelity model (case B): fuel and airline cost from one nominal performance per type. High-fidelity model (case C): the same from each aircraft's shared performance. High-fidelity model plus connections (case D): adds the airline's connection priority. Which options are considered is HLR-ATC-10's, and whether the one chosen has the lowest impact is HLR-ATC-05's, so the three do not overlap. The experiment's measure (fuel burned, and airline cost as fuel cost plus cost index times time, per aircraft and summed) is its representation of impact, not part of the requirement; what counts as impact stays open in the parent's measure (TBD, owner). Was 'ATC decision support shall determine the impact of each viable resolution option', tagged improved, verified against the truth model within a tolerance (D-040).";
        }
    }

    package AircraftSystemsRequirements {
        doc /* Aircraft Systems (D-007 modeled system; part aircraftSystems.aircraft and its avionics). */

        public import RequirementDefinitions::*;

        requirement <'HLR-ACF-01'> fmsPredictsPerformance : ConstituentSystemRequirement {
            doc /* The flight management system shall predict the flight's arrival time, fuel at the
             * destination, optimum altitude and maximum altitude from the entered weights, the
             * cost index and the forecast winds.
             */
            :>> status = RequirementStatus::draft;
            :>> kind = RequirementKind::functional;
            :>> constituentSystem = "Aircraft";
            :>> objectiveStatement = "The aircraft knows what it can fly and what is best for it.";
            :>> parentRequirements = SystemLevelRequirements::OnboardExecution::onboardPerformancePredictions;
            :>> verificationMethod = VerificationMethod::byInspection;
            :>> basis = EvidenceGrade::ownerExpertise;
            :>> evidenceRefs = "mori2022massCruise";
            :>> rationale = "Graded [SME]. The item FmsPerformancePrediction in nas_sysml_package_definitions.sysml. In the study: the on-board high-fidelity model. Its maximum altitude is the answer the rule of thumb replaces with 'at or below FL350'.";
        }

        requirement <'HLR-ACF-02'> clearedPathHeldByAutoflight : ConstituentSystemRequirement {
            doc /* The auto flight control system shall hold the aircraft on its cleared route,
             * altitude and speed within the tolerances of the airspace.
             */
            :>> status = RequirementStatus::draft;
            :>> kind = RequirementKind::performance;
            :>> constituentSystem = "Aircraft";
            :>> objectiveStatement = "The aircraft is where its clearance says it is.";
            :>> parentRequirements = SystemLevelRequirements::OnboardExecution::conformanceToClearedPath;
            :>> verificationMethod = VerificationMethod::byAnalysis;
            :>> measureOfPerformance = "cross-track distance from the cleared route; difference from the cleared altitude and speed";
            :>> unitOfMeasure = "NM, ft and Mach";
            :>> basis = EvidenceGrade::ownerExpertise;
            :>> rationale = "Graded [SME]. No tolerance is set. In the study: the deviation HLR-ATC-01 has to allow for.";
        }

        requirement <'HLR-ACF-03'> crewAlertedToLowPredictedFuel : ConstituentSystemRequirement {
            doc /* The flight management system shall alert the flight crew when the fuel it predicts
             * at the destination falls below the required reserve.
             */
            :>> status = RequirementStatus::draft;
            :>> kind = RequirementKind::functional;
            :>> constituentSystem = "Aircraft";
            :>> objectiveStatement = "The crew knows when a trajectory change has used up the fuel margin.";
            :>> parentRequirements = SystemLevelRequirements::OnboardExecution::lowFuelPredictionAlert;
            :>> verificationMethod = VerificationMethod::byInspection;
            :>> basis = EvidenceGrade::ownerExpertise;
            :>> rationale = "Graded [SME]. The parent SLR-EXE-06 also names dispatchers and controllers; they hear through the crew (HLR-CRW-04). In the study: fuel at the destination is a limit on which resolution an aircraft can accept.";
        }

        requirement <'HLR-ACF-04'> crewLinkedToAtcAndDispatcher : ConstituentSystemRequirement {
            doc /* The aircraft communication system shall carry voice and data between the flight crew
             * and both air traffic control and the dispatcher for the whole flight.
             */
            :>> status = RequirementStatus::draft;
            :>> kind = RequirementKind::interfaceRequirement;
            :>> constituentSystem = "Aircraft";
            :>> objectiveStatement = "Clearances, refusals, requests and reports to the airline can all be exchanged from the flight deck.";
            :>> parentRequirements = SystemLevelRequirements::ClearanceAndSeparation::controllerCrewCommunicationPath;
            :>> verificationMethod = VerificationMethod::byInspection;
            :>> basis = EvidenceGrade::ownerExpertise;
            :>> rationale = "Graded [SME]. In the study: every exchange the experiment counts as an instruction crosses this link.";
        }

        requirement <'HLR-ACF-05'> aircraftStateShared : ConstituentSystemRequirement {
            doc /* The aircraft shall make its current state available for sharing with the party
             * that decides changes to trajectories.
             */
            :>> status = RequirementStatus::draft;
            :>> kind = RequirementKind::interfaceRequirement;
            :>> constituentSystem = "Aircraft";
            :>> objectiveStatement = "The aircraft's state can reach the party that decides, by whichever system carries it (HLR-OPS-05).";
            :>> parentRequirements = (SystemLevelRequirements::InformationForTrajectoryDecisions::decisionInformationToDecidingParty, SystemLevelRequirements::OnboardExecution::onboardPerformancePredictions);
            :>> verificationMethod = VerificationMethod::byInspection;
            :>> basis = EvidenceGrade::ownerExpertise;
            :>> rationale = "The FMS-to-airline exchange named as one of the three on the thread in D-019 item 4. Whether aircraft do this today is for the owner to say [SME]; it is left as baseline because D-019 tags only the airline-to-ATC exchange as improved. In the study: the first link of the high-fidelity means. Owner (hand review 2026-10-20): 'The GW, CI & perf data can come from the flight and/or dispatch or the same computer system, whether the airline's or ATC's.' Reworded in the owner's hand review of 2026-11-05 (D-040): the aircraft, not the FMS, is the subject; 'its current state' replaces the list of figures; the route is left open.";
        }

        requirement <'HLR-ACF-06'> adsbStateBroadcast : ConstituentSystemRequirement {
            doc /* The aircraft's surveillance system shall broadcast the aircraft's position,
             * altitude, velocity and identity by ADS-B Out.
             */
            :>> status = RequirementStatus::draft;
            :>> kind = RequirementKind::interfaceRequirement;
            :>> constituentSystem = "Aircraft";
            :>> objectiveStatement = "The ground system and its conflict probe know where each aircraft is and where it is going.";
            :>> parentRequirements = (SystemLevelRequirements::ClearanceAndSeparation::conflictsPredicted, SystemLevelRequirements::ClearanceAndSeparation::separationMinimaMaintained);
            :>> verificationMethod = VerificationMethod::byInspection;
            :>> basis = EvidenceGrade::generalKnowledge;
            :>> evidenceRefs = "14 CFR 91.225";
            :>> rationale = "New. Owner (hand review 2026-10-20), beside HLR-ACF-05: 'Need one HLR for ADS-B data.' In the study: the surveillance input to ResolveConflict (ADS-B position reports, D-030) and the airspace domain's surveillanceIn port. The rule (14 CFR 91.225) is general knowledge, not yet tied to a held source. Wording is Claude's. Applied from a question on the owner's hand review of 2026-10-20; for the owner to confirm (D-031).";
        }
    }

    package AirportOperationsRequirements {
        doc /* Airport Operations (D-007 modeled system; part airportOperations.airport and its ground handling and fuelling). */

        public import RequirementDefinitions::*;

        requirement <'HLR-APT-01'> aircraftReadyByOffBlockTime : ConstituentSystemRequirement {
            doc /* Airport operations shall have each aircraft fuelled, loaded and sealed by its
             * scheduled off-block time.
             */
            :>> status = RequirementStatus::draft;
            :>> kind = RequirementKind::performance;
            :>> constituentSystem = "Airport operations";
            :>> objectiveStatement = "The flight leaves on schedule with its load complete.";
            :>> parentRequirements = SystemLevelRequirements::AirportAndSurface::aircraftReadyAtOffBlockTime;
            :>> verificationMethod = VerificationMethod::byDemonstration;
            :>> measureOfPerformance = "actual off-block time minus scheduled off-block time";
            :>> unitOfMeasure = "minutes";
            :>> basis = EvidenceGrade::literature;
            :>> evidenceRefs = "schultz2017turnaround";
            :>> rationale = "In the study: the weakest link of the five systems. It matters only because the weight is not final until loading ends.";
        }

        requirement <'HLR-APT-02'> actualFuelAndLoadReported : ConstituentSystemRequirement {
            doc /* Airport operations shall report the fuel uplifted and the load put on board to the
             * flight crew and the load planner before off-block.
             */
            :>> status = RequirementStatus::draft;
            :>> kind = RequirementKind::interfaceRequirement;
            :>> constituentSystem = "Airport operations";
            :>> objectiveStatement = "The weight used on board and by the airline is the weight the aircraft has.";
            :>> parentRequirements = (SystemLevelRequirements::AirportAndSurface::aircraftReadyAtOffBlockTime, SystemLevelRequirements::FlightPlanningAndRelease::preDepartureInformationToCrew);
            :>> verificationMethod = VerificationMethod::byInspection;
            :>> basis = EvidenceGrade::generalKnowledge;
            :>> rationale = "D-009 records the fuel slip reaching the crew from the airport fuel carrier; the load report is from general knowledge. In the study: the owner's note on SLR-APT-04, that it speaks to the unknowns in weights and to when the information is available.";
        }
    }

    package Allocation {
        doc /* Which part of NationalAirspaceSystem satisfies each requirement in this file.
         * The first part listed is the one accountable. */

        part hlrAllocation : NationalAirspaceSystem::NationalAirspaceSystem {

            // Flight crew
            satisfy requirement flightControlledAsCleared_crew :> ConstituentSystemRequirements::FlightCrewRequirements::flightControlledAsCleared by flightCrew.flightDeckCrew;
            satisfy requirement unflyableClearanceRefused_crew :> ConstituentSystemRequirements::FlightCrewRequirements::unflyableClearanceRefused by flightCrew.flightDeckCrew;
            satisfy requirement betterTrajectoryRequested_crew :> ConstituentSystemRequirements::FlightCrewRequirements::betterTrajectoryRequested by flightCrew.flightDeckCrew;
            satisfy requirement dispatcherToldOfTrajectoryChanges_crew :> ConstituentSystemRequirements::FlightCrewRequirements::dispatcherToldOfTrajectoryChanges by flightCrew.flightDeckCrew;
            satisfy requirement weightsAndCostIndexEnteredInFms_crew :> ConstituentSystemRequirements::FlightCrewRequirements::weightsAndCostIndexEnteredInFms by flightCrew.flightDeckCrew;

            // Flight operations
            satisfy requirement flightPlannedFromAircraftPerformance_aocDs :> ConstituentSystemRequirements::FlightOperationsRequirements::flightPlannedFromAircraftPerformance by flightOperations.airlineOperationsCenter.decisionSupport;
            satisfy requirement flightPlannedFromAircraftPerformance_dispatcher :> ConstituentSystemRequirements::FlightOperationsRequirements::flightPlannedFromAircraftPerformance by flightOperations.airlineOperationsCenter.dispatcher;
            satisfy requirement flightPlannedFromAircraftPerformance_loadPlanner :> ConstituentSystemRequirements::FlightOperationsRequirements::flightPlannedFromAircraftPerformance by flightOperations.airlineOperationsCenter.loadPlanner;
            satisfy requirement flightPlanFiledByDispatcher_dispatcher :> ConstituentSystemRequirements::FlightOperationsRequirements::flightPlanFiledByDispatcher by flightOperations.airlineOperationsCenter.dispatcher;
            satisfy requirement releasePackageGivenToCrew_dispatcher :> ConstituentSystemRequirements::FlightOperationsRequirements::releasePackageGivenToCrew by flightOperations.airlineOperationsCenter.dispatcher;
            satisfy requirement releasePackageGivenToCrew_loadPlanner :> ConstituentSystemRequirements::FlightOperationsRequirements::releasePackageGivenToCrew by flightOperations.airlineOperationsCenter.loadPlanner;
            satisfy requirement dispatcherReleasesWithCaptain_dispatcher :> ConstituentSystemRequirements::FlightOperationsRequirements::dispatcherReleasesWithCaptain by flightOperations.airlineOperationsCenter.dispatcher;
            satisfy requirement performanceShareProvided_aoc :> ConstituentSystemRequirements::FlightOperationsRequirements::performanceShareProvided by flightOperations.airlineOperationsCenter;
            satisfy requirement flightRePlannedWithCrew_dispatcher :> ConstituentSystemRequirements::FlightOperationsRequirements::flightRePlannedWithCrew by flightOperations.airlineOperationsCenter.dispatcher;
            satisfy requirement fuelAndCo2ReportedByAirline_aoc :> ConstituentSystemRequirements::FlightOperationsRequirements::fuelAndCo2ReportedByAirline by flightOperations.airlineOperationsCenter;

            // Air traffic control
            satisfy requirement separationKeptWithConformanceMargin_atc :> ConstituentSystemRequirements::AirspaceManagementRequirements::separationKeptWithConformanceMargin by airspaceManagement.atc;
            satisfy requirement separationKeptWithConformanceMargin_artcc :> ConstituentSystemRequirements::AirspaceManagementRequirements::separationKeptWithConformanceMargin by airspaceManagement.artcc;
            satisfy requirement controllerAlertedToPredictedConflict_atcDs :> ConstituentSystemRequirements::AirspaceManagementRequirements::controllerAlertedToPredictedConflict by airspaceManagement.atc.decisionSupport;
            satisfy requirement filedIntentShownToController_artcc :> ConstituentSystemRequirements::AirspaceManagementRequirements::filedIntentShownToController by airspaceManagement.artcc;
            satisfy requirement conflictResolvedWithFlyableClearance_atc :> ConstituentSystemRequirements::AirspaceManagementRequirements::conflictResolvedWithFlyableClearance by airspaceManagement.atc;
            satisfy requirement conflictResolvedWithFlyableClearance_atcDs :> ConstituentSystemRequirements::AirspaceManagementRequirements::conflictResolvedWithFlyableClearance by airspaceManagement.atc.decisionSupport;
            satisfy requirement lowestImpactResolutionChosen_atc :> ConstituentSystemRequirements::AirspaceManagementRequirements::lowestImpactResolutionChosen by airspaceManagement.atc;
            satisfy requirement conflictResolvedWithinWorkload_atc :> ConstituentSystemRequirements::AirspaceManagementRequirements::conflictResolvedWithinWorkload by airspaceManagement.atc;
            satisfy requirement crewRequestAnsweredByController_atc :> ConstituentSystemRequirements::AirspaceManagementRequirements::crewRequestAnsweredByController by airspaceManagement.atc;
            satisfy requirement performanceShareUsedInResolution_atcDs :> ConstituentSystemRequirements::AirspaceManagementRequirements::performanceShareUsedInResolution by airspaceManagement.atc.decisionSupport;
            satisfy requirement viableOptionsDetermined_atc :> ConstituentSystemRequirements::AirspaceManagementRequirements::viableOptionsDetermined by airspaceManagement.atc;
            satisfy requirement viableOptionsDetermined_atcDs :> ConstituentSystemRequirements::AirspaceManagementRequirements::viableOptionsDetermined by airspaceManagement.atc.decisionSupport;
            satisfy requirement optionImpactDetermined_atc :> ConstituentSystemRequirements::AirspaceManagementRequirements::optionImpactDetermined by airspaceManagement.atc;
            satisfy requirement optionImpactDetermined_atcDs :>ConstituentSystemRequirements::AirspaceManagementRequirements::optionImpactDetermined by airspaceManagement.atc.decisionSupport;
            satisfy requirement clearancesRecorded_atc :> ConstituentSystemRequirements::AirspaceManagementRequirements::clearancesRecorded by airspaceManagement.atc;

            // Aircraft
            satisfy requirement fmsPredictsPerformance_fms :> ConstituentSystemRequirements::AircraftSystemsRequirements::fmsPredictsPerformance by aircraftSystems.aircraft.avionics.flightManagementSystem;
            satisfy requirement clearedPathHeldByAutoflight_autoflight :> ConstituentSystemRequirements::AircraftSystemsRequirements::clearedPathHeldByAutoflight by aircraftSystems.aircraft.avionics.autoFlightControlSystem;
            satisfy requirement clearedPathHeldByAutoflight_fms :> ConstituentSystemRequirements::AircraftSystemsRequirements::clearedPathHeldByAutoflight by aircraftSystems.aircraft.avionics.flightManagementSystem;
            satisfy requirement crewAlertedToLowPredictedFuel_fms :> ConstituentSystemRequirements::AircraftSystemsRequirements::crewAlertedToLowPredictedFuel by aircraftSystems.aircraft.avionics.flightManagementSystem;
            satisfy requirement crewLinkedToAtcAndDispatcher_comms :> ConstituentSystemRequirements::AircraftSystemsRequirements::crewLinkedToAtcAndDispatcher by aircraftSystems.aircraft.avionics.communicationSystem;
            satisfy requirement aircraftStateShared_fms :> ConstituentSystemRequirements::AircraftSystemsRequirements::aircraftStateShared by aircraftSystems.aircraft.avionics.flightManagementSystem;
            satisfy requirement aircraftStateShared_comms :> ConstituentSystemRequirements::AircraftSystemsRequirements::aircraftStateShared by aircraftSystems.aircraft.avionics.communicationSystem;

            satisfy requirement adsbStateBroadcast_surveillance :> ConstituentSystemRequirements::AircraftSystemsRequirements::adsbStateBroadcast by aircraftSystems.aircraft.avionics.surveillanceSystem;
            // Airport operations
            satisfy requirement aircraftReadyByOffBlockTime_groundHandling :> ConstituentSystemRequirements::AirportOperationsRequirements::aircraftReadyByOffBlockTime by airportOperations.airport.groundHandling;
            satisfy requirement aircraftReadyByOffBlockTime_fuelling :> ConstituentSystemRequirements::AirportOperationsRequirements::aircraftReadyByOffBlockTime by airportOperations.airport.fuelDistributionSystem;
            satisfy requirement actualFuelAndLoadReported_fuelling :> ConstituentSystemRequirements::AirportOperationsRequirements::actualFuelAndLoadReported by airportOperations.airport.fuelDistributionSystem;
            satisfy requirement actualFuelAndLoadReported_groundHandling :> ConstituentSystemRequirements::AirportOperationsRequirements::actualFuelAndLoadReported by airportOperations.airport.groundHandling;
        }
    }
}
